module ietf-l2vpn {
  namespace "urn:ietf:params:xml:ns:yang:ietf-l2vpn";
  prefix "l2vpn";

  import ietf-inet-types {
    prefix "inet";
  }

  import ietf-yang-types {
    prefix "yang";
  }

  import ietf-mpls {
    prefix "mpls";
    revision-date 2017-08-02;
  }

  import ietf-routing-types {
    prefix "rt-types";
    revision-date 2017-08-02;
  }

  import network-topology {
    prefix nt;
    revision-date 2013-10-21;
  }

  import yang-ext {
    prefix ext;
    revision-date "2013-07-09";
  }

  organization  "ietf";
  contact       "ietf";
  description   "l2vpn";

  revision 2017-08-02 {
    description
      "Made YANG module compatible with ODL.";
  }

  revision "2017-03-06" {
    description "Sixth revision " +
                "  - Removed the 'common' container and move pw-templates " +
                "    and redundancy-group-templates up a level " +
                "  - Consolidated the endpoint configuration such that " +
                "    all L2VPN instances has a list of endpoint.  For " +
                "    certain types of L2VPN instances such as VPWS where " +
                "    each L2VPN instance is limited to at most two " +
                "    endpoint, additional augment statements were included " +
                "    to add necessary constraints " +
                "  - Removed discovery-type and signaling-type operational " +
                "    state from VPLS pseudowires, as these two parameters " +
                "    are configured as L2VPN parameters rather than " +
                "    pseudowire paramteres " +
                "  - Renamed l2vpn-instances to l2vpn-instances-state " +
                "    in the operational state branch " +
                "  - Removed BGP parameter groupings and reused " +
                "    ietf-routing-types.yang module instead " +
                "";
    reference "";
  }

  revision "2016-10-24" {
    description "Fifth revision " +
                "  - Edits based on Giles's comments " +
                "    5) Remove relative leafrefs in groupings, " +
                "       and the resulting new groupings are: " +
                "       (a) bgp-auto-discovery-parameters-grp " +
                "       (b) bgp-signaling-parameters-grp " +
                "       (c) endpoint-grp " +
                "    11) Merge VPLS and VPWS into one single list " +
                "       and use augment statements to handle " +
                "       differences between VPLS and VPWS " +
                "  - Add a new grouping l2vpn-common-parameters-grp " +
                "    to make VPLS and VPWS more consistent";
    reference "";
  }

  revision "2016-05-31" {
    description "Fourth revision " +
                "  - Edits based on Giles's comments " +
                "    1) Change enumeration to identityref type for: " +
                "       (a) l2vpn-service-type " +
                "       (b) l2vpn-discovery-type " +
                "       (c) l2vpn-signaling-type " +
                "       bgp-rt-type, cw-negotiation, and " +
                "       pbb-component remain enumerations " +
                "    2) Define i-sid-type for leaf 'i-sid' " +
                "       (which is renamed from 'i-tag') " +
                "    3) Rename 'vpn-targets' to 'vpn-target' " +
                "    4) Import ietf-mpls.yang and reuse the " +
                "       'mpls-label' type defined in ietf-mpls.yang " +
                "       transmit-label and receive-label " +
                "    8) Change endpoint list's key to name " +
                "    9) Changed MTU to type uint16 " +
                "";
    reference "";
  }

  revision "2016-03-07" {
    description "Third revision " +
                "  - Changed the module name to ietf-l2vpn " +
                "  - Merged EVPN into L2VPN " +
                "  - Eliminated the definitions of attachment " +
                "    circuit with the intention to reuse other " +
                "    layer-2 definitions " +
                "  - Added state branch";
    reference "";
  }

  revision "2015-10-08" {
    description "Second revision " +
                "  - Added container vpls-instances " +
                "  - Rearranged groupings and typedefs to be " +
                "    reused across vpls-instance and vpws-instances";
    reference "";
  }

  revision "2015-06-30" {
    description "Initial revision";
    reference   "";
  }

  /* identities */

  identity l2vpn-instance-type {
    description "Base identity from which identities of " +
                "l2vpn service instance types are derived";
  }

  identity vpws-instance-type {
    base l2vpn-instance-type;
    description "This identity represents VPWS instance type";
  }

  identity vpls-instance-type {
    base l2vpn-instance-type;
    description "This identity represents VPLS instance type";
  }

  identity link-discovery-protocol {
    description "Base identiy from which identities describing " +
                "link discovery protocols are derived";
  }

  identity lacp {
    base "link-discovery-protocol";
    description "This identity represents LACP";
  }

  identity lldp {
    base "link-discovery-protocol";
    description "This identity represents LLDP";
  }

  identity bpdu {
    base "link-discovery-protocol";
    description "This identity represens BPDU";
  }

  identity cpd {
    base "link-discovery-protocol";
    description "This identity represents CPD";
  }

  identity udld {
    base "link-discovery-protocol";
    description "This identity represens UDLD";
  }

  identity l2vpn-service {
    description "Base identity from which identities describing " +
                "L2VPN services are derived";
  }

  identity Ethernet {
    base "l2vpn-service";
    description "This identity represents Ethernet service";
  }

  identity ATM {
    base "l2vpn-service";
    description "This identity represents Asynchronous Transfer " +
                "Mode service";
  }

  identity FR {
    base "l2vpn-service";
    description "This identity represent Frame-Relay service";
  }

  identity TDM {
    base "l2vpn-service";
    description "This identity represent Time Devision " +
                "Multiplexing service";
  }

  identity l2vpn-discovery {
    description "Base identity from which identities describing " +
                "L2VPN discovery protocols are derived";
  }

  identity manual-discovery {
    base "l2vpn-discovery";
    description "Manual configuration of l2vpn service";
  }

  identity bgp-auto-discovery {
    base "l2vpn-discovery";
    description "Border Gateway Protocol (BGP) auto-discovery of " +
                "l2vpn service";
  }

  identity ldp-discovery {
    base "l2vpn-discovery";
    description "Label Distribution Protocol (LDP) discovery of " +
                "l2vpn service";
  }

  identity mixed-discovery {
    base "l2vpn-discovery";
    description "Mixed discovery methods of l2vpn service";
  }

  identity l2vpn-signaling {
    description "Base identity from which identities describing " +
                "L2VPN signaling protocols are derived";
  }

  identity static-configuration {
    base "l2vpn-signaling";
    description "Static configuration of labels (no signaling)";
  }

  identity ldp-signaling {
    base "l2vpn-signaling";
    description "Label Distribution Protocol (LDP) signaling";
  }

  identity bgp-signaling {
    base "l2vpn-signaling";
    description "Border Gateway Protocol (BGP) signaling";
  }

  identity mixed-signaling {
    base "l2vpn-signaling";
    description "Mixed signaling methods";
  }

  /* typedefs */

  typedef l2vpn-service-type {
    type identityref {
      base "l2vpn-service";
    }
    description "L2VPN service type";
  }

  typedef l2vpn-discovery-type {
    type identityref {
      base "l2vpn-discovery";
    }
    description "L2VPN discovery type";
  }

  typedef l2vpn-signaling-type {
    type identityref {
      base "l2vpn-signaling";
    }
    description "L2VPN signaling type";
  }

  typedef cw-negotiation-type {
    type enumeration {
      enum "non-preferred" {
        description "No preference for control-word";
      }
      enum "preferred" {
        description "Prefer to have control-word negotiation";
      }
    }
    description "control-word negotiation preference type";
  }

  typedef link-discovery-protocol-type {
    type identityref {
      base "link-discovery-protocol";
    }
    description "This type is used to identify " +
                "link discovery protocol";
  }

  typedef pbb-component-type {
    type enumeration {
      enum "b-component" {
        description "Identifies as a b-component";
      }
      enum "i-component" {
        description "Identifies as an i-component";
      }
    }
    description "This type is used to identify " +
                "the type of PBB component";
  }

  typedef pw-template-ref {
    type leafref {
      path "/l2vpn/pw-templates/pw-template/name";
    }
    description "pw-template-ref";
  }

  typedef redundancy-group-template-ref {
    type leafref {
      path "/l2vpn/redundancy-group-templates" +
           "/redundancy-group-template/name";
    }
    description "redundancy-group-template-ref";
  }

  typedef l2vpn-instance-name-ref {
    type leafref {
      path "/l2vpn/l2vpn-instances" +
           "/l2vpn-instance/name";
    }
    description "l2vpn-instance-name-ref";
  }

  typedef l2vpn-instance-type-ref {
    type leafref {
      path "/l2vpn/l2vpn-instances" +
           "/l2vpn-instance/type";
    }
    description "l2vpn-instance-type-ref";
  }

  typedef operational-state-type {
    type enumeration {
      enum 'up' {
        description "Operational state is up";
      }
      enum 'down' {
        description "Operational state is down";
      }
    }
    description "operational-state-type";
  }

  typedef i-sid-type {
    type uint32 {
      range "0..16777216";
    }
    description "I-SID type that is 24-bits. " +
                "This should be moved to ieee-types.yang at " +
                "http://www.ieee802.org/1/files/public/docs2015" +
                "/new-mholness-ieee-types-yang-v01.yang";
  }

  /* groupings */

  grouping pbb-parameters-grp {
    description "PBB parameters grouping";
    container pbb-parameters {
      description "pbb-parameters";
      choice component-type {
        description "PBB component type";
        case i-component {
          leaf i-sid {
            type i-sid-type;
            description "I-SID";
          }
          leaf backbone-src-mac {
            type yang:mac-address;
            description "backbone-src-mac";
          }
        }
        case b-component {
          leaf bind-b-component-name {
            type l2vpn-instance-name-ref;
            must "/l2vpn" +
                 "/l2vpn-instances/l2vpn-instance[name=current()]" +
                 "/type = 'vpls-instance-type'" {
              description "A b-component must be an L2VPN instance " +
                          "of type vpls-instance-type";
            }
            description "Reference to the associated b-component";
          }
        }
      }
    }
  }

  grouping pbb-parameters-state-grp {
    description "PBB parameters grouping";
    container pbb-parameters {
      description "pbb-parameters";
      choice component-type {
        description "PBB component type";
        case i-component {
          leaf i-sid {
            type i-sid-type;
            description "I-SID";
          }
          leaf backbone-src-mac {
            type yang:mac-address;
            description "backbone-src-mac";
          }
        }
        case b-component {
          leaf bind-b-component-name {
            type string;
            description "Name of the associated b-component";
          }
          leaf bind-b-component-type {
            type identityref {
              base l2vpn-instance-type;
            }
            must ". = 'vpls-instance-type'" {
              description "The associated b-component must have " +
                          "type vpls-instance-type";
            }
            description "Type of the associated b-component";
          }
        }
      }
    }
  }

  grouping l2vpn-common-parameters-grp {
    description "L2VPN common parameters";
    leaf name {
      type string;
      description "Name of L2VPN service instance";
    }
    leaf type {
      type identityref {
        base l2vpn-instance-type;
      }
      description "Type of L2VPN service instance";
    }
    leaf mtu {
      type uint16;
      description "MTU of L2VPN service";
    }
    leaf mac-aging-timer {
      type uint32;
      description "mac-aging-timer, the duration after which" +
                  "a MAC entry is considered aged out";
    }
    leaf service-type {
      type l2vpn-service-type;
      default Ethernet;
      description "L2VPN service type";
    }
    leaf discovery-type {
      type l2vpn-discovery-type;
      default manual-discovery;
      description "L2VPN service discovery type";
    }
    leaf signaling-type {
      type l2vpn-signaling-type;
      mandatory true;
      description "L2VPN signaling type";
    }
  }

  grouping bgp-signaling-parameters-grp {
    description "BGP parameters for signaling";
    leaf site-id {
      type uint16;
      description "Site ID";
    }
    leaf site-range {
      type uint16;
      description "Site Range";
    }
  }

  grouping pw-common-parameters-grp {
    description "Pseudowire parameters common to both " +
                "VPWS and VPLS pseudowires";
    leaf name {
      type string;
      description "pseudowire name";
    }
    leaf template {
      type pw-template-ref;
      description "pseudowire template";
    }
    leaf mtu {
      type uint16;
      description "PW MTU";
    }
    leaf mac-withdraw {
      type boolean;
      default false;
      description "Enable (true) or disable (false) MAC withdraw";
    }
    leaf cw-negotiation {
      type cw-negotiation-type;
      description "cw-negotiation";
    }
    leaf tunnel-policy {
      type string;
      description "tunnel policy name";
    }
    uses pw-type-grp;
  }

  grouping pw-type-grp {
    description "pseudowire type grouping";
    choice pw-type {
      description "A choice of pseudowire type";
      case ldp-or-static-pw {
        leaf peer-ip {
          type inet:ip-address;
          description "peer IP address";
        }
        leaf pw-id {
          type uint32;
          description "pseudowire id";
        }
        leaf icb {
          type boolean;
          description "inter-chassis backup";
        }
      }
      case bgp-pw {
        leaf remote-pe-id {
          type inet:ip-address;
          description "remote pe id";
        }
      }
      case bgp-ad-pw {
        leaf remote-ve-id {
          type uint16;
          description "remote ve id";
        }
      }
    }
  }

  grouping redundancy-group-properties-grp {
    description "redundancy-group-properties-grp";
    leaf protection-mode {
      type enumeration {
        enum "frr" {
          value 0;
          description "fast reroute";
        }
        enum "master-slave" {
          value 1;
          description "master-slave";
        }
        enum "independent" {
          value 2;
          description "independent";
        }
      }
      description "protection-mode";
    }
    leaf reroute-mode {
      type enumeration {
        enum "immediate" {
          value 0;
          description "immediate reroute";
        }
        enum "delayed" {
          value 1;
          description "delayed reroute";
        }
        enum "never" {
          value 2;
          description "never reroute";
        }
      }
      description "reroute-mode";
    }
    leaf dual-receive {
      type boolean;
      description
      "allow extra traffic to be carried by backup";
    }
    leaf revert {
      type boolean;
      description "allow forwarding to revert to primary " +
                  "after restoring primary";
    }
    leaf reroute-delay {
      when "../reroute-mode = 'delayed'" {
        description "Specify amount of time to " +
                    "delay reroute only when " +
                    "delayed route is configured";
      }
      type uint16;
      description "amount of time to delay reroute";
    }
    leaf revert-delay {
      when "../revert = 'true'" {
        description "Specify the amount of time to " +
                    "wait to revert to primary " +
                    "only if reversion is configured";
      }
      type uint16;
      description "amount ot time to wait to revert to primary";
    }
  }

  grouping endpoint-grp {
    description "A grouping that defines the structure of " +
                "an endpoint";
    leaf name {
      type string;
      description "endpoint name";
    }
    choice ac-or-pw-or-redundancy-grp-choice {
      description "A choice of attachment circuit or " +
                  "pseudowire or redundancy group";
      case ac-case {
        description "Attachment circuit(s) as an endpoint";
        list ac {
          key "name";
          leaf name {
            type string;
            description "Name of attachment circuit.  " +
                        "This field is intended to " +
                        "reference standardized " +
                        "layer-2 definitions.";
          }
          description "An L2VPN instance's " +
                      "attachment circuit list";
        }
      }
      case pw-case {
        description "Pseudowire(s) as an endpoint";
        list pw {
          key "name";
          leaf name {
            type leafref {
              path "/l2vpn/l2vpn-instances/l2vpn-instance/pw/name";
            }
            description "name of pseudowire";
          }
          description "An L2VPN instance's pseudowire list";
        }
      }
      case redundancy-grp-case {
        description "Redundancy group as an endpoint";
        choice primary {
          mandatory true;
          description "primary options";
          case primary-ac {
            description "primary-ac";
          }
          case primary-pw {
            description "primary-pw";
          }
        }
        choice backup-choice {
          description "backup options";
          case backup-ac-case {
            description "backup-ac";
          }
          case backup-pw-case {
            description "backup-pw";
          }
        }
        leaf template {
          type leafref {
            path "/l2vpn/redundancy-group-templates" +
                 "/redundancy-group-template/name";
          }
          description "Reference a redundancy group " +
                      "properties template";
        }
        uses redundancy-group-properties-grp;
      }
    }
  }

  grouping ac-state-grp {
    description "ac-state-grp";
    leaf name {
      type string;
      description "Name of attachment circuit.  " +
                  "This field is intended to " +
                  "reference standardized " +
                  "layer-2 definitions.";
    }
    leaf state {
      type operational-state-type;
      description "attachment circuit up/down state";
    }
  }
  grouping common-pw-state-grp {
    description "common-pw-state-grp";
    leaf name {
      type string;
      description "pseudowire name";
    }
    leaf state {
      type operational-state-type;
      description "pseudowire operation state up/down";
    }
    leaf mtu {
      type uint16;
      description "PW MTU";
    }
    leaf mac-withdraw {
      type boolean;
      description "MAC withdraw is enabled (ture) or disabled (false)";
    }
    leaf cw-negotiation {
      type cw-negotiation-type;
      description "Override the control-word negotiation " +
                  "preference specified in the " +
                  "pseudowire template.";
    }
    leaf tunnel-policy {
      type string;
      description "Used to override the tunnel policy name " +
                  "specified in the pseduowire template";
    }
    uses pw-type-grp;
  }

  grouping vpws-only-pw-state-grp {
    description "vpws-pw-state-grp";
    leaf vccv-ability {
      type boolean;
      description "vccv-ability";
    }
    leaf request-vlanid {
      type uint16;
      description "request vlanid";
    }
    leaf vlan-tpid {
      type string;
      description "vlan tpid";
    }
    leaf ttl {
      type uint8;
      description "time-to-live";
    }
  }

  /* L2VPN YANG Model */

  container l2vpn {
    description "l2vpn";
    container pw-templates {
      description "pw-templates";
      list pw-template {
        key "name";
        description "pw-template";
        leaf name {
          type string;
          description "name";
        }
        leaf mtu {
          type uint16;
          description "pseudowire mtu";
        }
        leaf cw-negotiation {
          type cw-negotiation-type;
          default "preferred";
          description
            "control-word negotiation preference";
        }
        leaf tunnel-policy {
          type string;
          description "tunnel policy name";
        }
      }
    }
    container redundancy-group-templates {
      description "redundancy group templates";
      list redundancy-group-template {
        key "name";
        description "redundancy-group-template";
        leaf name {
          type string;
          description "name";
        }
        uses redundancy-group-properties-grp;
      }
    }
    container l2vpn-instances {
      description "A list of L2VPN instances";
      list l2vpn-instance {
        key "name type";
        description "An L2VPN service instance";
        uses l2vpn-common-parameters-grp;
        container bgp-auto-discovery {
          description "BGP auto-discovery parameters";
          leaf route-distinguisher {
            type rt-types:route-distinguisher;
            description "BGP route distinguisher";
          }
          leaf vpn-id {
            type string;
            description "VPN ID";
          }
          uses rt-types:vpn-route-targets;
        }
        container bgp-signaling {
          when "../signaling-type = 'bgp-signaling'" {
            description "Check signaling type: " +
                        "Can only configure BGP signaling if " +
                        "signaling type is BGP";
          }
          description "BGP signaling parameters";
          uses bgp-signaling-parameters-grp;
        }
        list pw {
          key "name";
          description "A pseudowire";
          uses pw-common-parameters-grp;
        }
        list endpoint {
          key "name";
          description "An endpoint";
          uses endpoint-grp;
        }
      }
    }
  }

  container l2vpn-state {
    config false;
    description "l2vpn state";
    container l2vpn-instances-state {
      description "L2VPN instances state";
      list l2vpn-instance {
        description "An L2VPN instance's state";
        uses l2vpn-common-parameters-grp;
        container bgp-auto-discovery {
          description "BGP auto-discovery parameters";
          leaf route-distinguisher {
            type rt-types:route-distinguisher;
            description "BGP route distinguisher";
          }
          leaf vpn-id {
            type string;
            description "VPN ID";
          }
          uses rt-types:vpn-route-targets;
        }
        container bgp-signaling {
          description "BGP signaling parameters";
          uses bgp-signaling-parameters-grp;
        }
        list endpoint {
          key "name";
          description "An endpoint";
          uses endpoint-grp;
        }
      }
    }
  }

  /* augments */

  augment "/l2vpn/l2vpn-instances/l2vpn-instance" {
    when "type = 'vpws-instance-type'" {
      description "Constraints only for VPWS pseudowires";
    }
    description "Augment for VPWS instance";
    container vpws-constraints {
      must "(count(../endpoint) <= 2) and " +
           "(count(../endpoint/pw) <= 1) and " +
           "(count(../endpoint/ac) <= 1) and " +
           "(count(../endpoint/primary-pw) <= 1) and " +
           "(count(../endpoint/backup-pw) <= 1) " {
        description "A VPWS L2VPN instance has at most 2 endpoints " +
                    "and each endpoint has at most 1 pseudowire or " +
                    "1 attachment circuit";
      }
      description "VPWS constraints";
    }
  }

  augment "/l2vpn/l2vpn-instances/l2vpn-instance/pw" {
    when "../type = 'vpws-instance-type'" {
      description "Pseudowire parameters only for VPWS pseudowires";
    }
    description "Augment for peudowire parameters for " +
                "VPWS pseudowires";
    ext:augment-identifier "vpws-pw-aug";
    leaf vccv-ability {
      type boolean;
      description "vccvability";
    }
    leaf request-vlanid {
      type uint16;
      description "request vlanid";
    }
    leaf vlan-tpid {
      type string;
      description "vlan tpid";
    }
    leaf ttl {
      type uint8;
      description "time-to-live";
    }
  }

  augment "/l2vpn/l2vpn-instances/l2vpn-instance" {
    when "type = 'vpls-instance-type'" {
      description "Parameters specifically for a VPLS instance";
    }
    description "Augment for parameters for a VPLS instance";
    uses pbb-parameters-grp;
  }

  augment "/l2vpn/l2vpn-instances/l2vpn-instance/endpoint" {
    when "../type = 'vpls-instance-type'" {
      description "Endpoint parameter specifically for " +
                  "a VPLS instance";
    }
    description "Augment for endpoint parameters for a VPLS instance";
    leaf split-horizon-group {
      type string;
      description "Identify a split horizon group";
    }
  }

  augment "/l2vpn/l2vpn-instances/l2vpn-instance/endpoint" +
          "/ac-or-pw-or-redundancy-grp-choice/redundancy-grp-case" +
          "/backup-choice/backup-pw-case/backup-pw" {
    when "../../type = 'vpls-instance-type'" {
      description "Backup pseudowire parameter specifically for " +
                  "a VPLS instance";
    }
    description "Augment for backup pseudowire paramters for " +
                "a VPLS instance";
    leaf precedence {
      type uint32;
      description "precedence of the pseudowire";
    }
  }

  augment "/l2vpn-state/l2vpn-instances-state/l2vpn-instance" +
          "/endpoint/ac-or-pw-or-redundancy-grp-choice/pw-case/pw" {
    when "../../type = 'vpws-instance-type'" {
      description "Additional operational state specifically for " +
                  "a VPWS instance's pseudowire endpoint";
    }
    description "Augment for a VPWS instance's pseudowire endpoint " +
                "operational state";
    uses vpws-only-pw-state-grp;
  }

  augment "/l2vpn-state/l2vpn-instances-state/l2vpn-instance" +
          "/endpoint/ac-or-pw-or-redundancy-grp-choice/redundancy-grp-case" +
          "/primary/primary-pw/primary-pw" {
    when "../../type = 'vpws-instance-type'" {
      description "Additional operational state specifically for " +
                  "a VPWS instance's primary pseudowire endpoint";
    }
    description "Augment for a VPWS instance's primary pseudowire " +
                "endpoint operational state";
    uses vpws-only-pw-state-grp;
  }

  augment "/l2vpn-state/l2vpn-instances-state/l2vpn-instance" +
          "/endpoint/ac-or-pw-or-redundancy-grp-choice/redundancy-grp-case" +
          "/backup-choice/backup-pw-case/backup-pw" {
    when "../../type = 'vpws-instance-type'" {
      description "Additional operational state specifically for " +
                  "a VPWS instance's backup pseudowire endpoint";
    }
    description "Augment for a VPWS instance's backup pseudowire " +
                "endpoint operational state";
    uses vpws-only-pw-state-grp;
  }

  augment "/l2vpn-state/l2vpn-instances-state/l2vpn-instance" +
          "/endpoint" {
    when "../type = 'vpls-instance-type'" {
      description "Endpoint parameter specifically for " +
                  "a VPLS instance operational state";
    }
    description "Augment for endpoint parameters for a VPLS " +
                "instance operational state";
    leaf split-horizon-group {
      type string;
      description "Identify a split horizon group";
    }
  }
  augment "/l2vpn-state/l2vpn-instances-state/l2vpn-instance" {
    when "type = 'vpls-instance-type'" {
      description "Additional operational state specifically for " +
                  "a VPLS instance";
    }
    description "Augment for a VPLS instance's " +
                "operational state";
    uses pbb-parameters-state-grp;
  }

  augment "/l2vpn-state/l2vpn-instances-state/l2vpn-instance" +
          "/endpoint/ac-or-pw-or-redundancy-grp-choice/redundancy-grp-case" +
          "/backup-choice/backup-pw-case/backup-pw" {
    when "../../type = 'vpls-instance-type'" {
      description "Additional operational state specifically for " +
                  "a VPLS instance's backup pseudowire endpoint";
    }
    description "Augment for a VPLS instance's backup pseudowire " +
                "endpoint operational state";
    leaf precedence {
      type uint32;
      description "precedence of the pseudowire";
    }
  }

  augment "/l2vpn/l2vpn-instances/l2vpn-instance/endpoint/ac-or-pw-or-redundancy-grp-choice/redundancy-grp-case/" +
          "primary/primary-ac" {
    description "Augment for primary-ac";
    leaf primary-ac {
      type string;
      description "Name of primary attachment circuit.  " +
                  "This field is intended to reference " +
                  "standardized layer-2 definitions.";
    }
  }
  augment "/l2vpn/l2vpn-instances/l2vpn-instance/endpoint/ac-or-pw-or-redundancy-grp-choice/redundancy-grp-case/" +
          "primary/primary-pw" {
    description "Augment for primary-pw";
    list primary-pw {
      key "name";
      leaf name {
        type leafref {
          path "/l2vpn/l2vpn-instances/l2vpn-instance/pw/name";
        }
        description "name of pseudowire";
      }
      description "An L2VPN instance's pseudowire list";
    }
  }
  augment "/l2vpn/l2vpn-instances/l2vpn-instance/endpoint/ac-or-pw-or-redundancy-grp-choice/redundancy-grp-case/" +
          "backup-choice/backup-ac-case" {
    description "Augment for backup-ac";
    leaf backup-ac {
      type string;
      description "Name of backup attachment circuit.  " +
                  "This field is intended to reference " +
                  "standardized layer-2 definitions.";
    }
  }
  augment "/l2vpn/l2vpn-instances/l2vpn-instance/endpoint/ac-or-pw-or-redundancy-grp-choice/redundancy-grp-case/" +
          "backup-choice/backup-pw-case" {
    description "Augment for backup-pw";
    list backup-pw {
      key "name";
      leaf name {
        type leafref {
          path "/l2vpn/l2vpn-instances/l2vpn-instance/pw/name";
        }
        description "Reference an attachment circuit";
      }
      description "A list of backup pseudowires";
    }
  }

  augment "/l2vpn-state/l2vpn-instances-state/l2vpn-instance/endpoint/ac-or-pw-or-redundancy-grp-choice/ac-case" {
    description "Augment of attachment circuit state";
    list ac {
      uses ac-state-grp;
      description "An attachment circuit's " +
                  "operational state";
    }
  }
  augment "/l2vpn-state/l2vpn-instances-state/l2vpn-instance/endpoint/ac-or-pw-or-redundancy-grp-choice/pw-case" {
    description "Augment of pseudowire state";
    list pw {
      uses common-pw-state-grp;
      description "A pseudowire's operational state";
    }
  }
  augment "/l2vpn-state/l2vpn-instances-state/l2vpn-instance/endpoint/ac-or-pw-or-redundancy-grp-choice/redundancy-grp-case/" +
          "primary/primary-ac" {
    description "Augment of primary attachment circuit state";
    container primary-ac {
      uses ac-state-grp;
      description "An attachment circuit's " +
                  "operational state";
    }
  }
  augment "/l2vpn-state/l2vpn-instances-state/l2vpn-instance/endpoint/ac-or-pw-or-redundancy-grp-choice/redundancy-grp-case/" +
          "primary/primary-pw" {
    description "Augment of primary pseudowire state";
    list primary-pw {
      uses common-pw-state-grp;
      description "A pseudowire's operational state";
    }
  }
  augment "/l2vpn-state/l2vpn-instances-state/l2vpn-instance/endpoint/ac-or-pw-or-redundancy-grp-choice/redundancy-grp-case/" +
          "backup-choice/backup-ac-case" {
    description "Augment of backup attachment circuit state";
    container backup-ac {
      uses ac-state-grp;
      description "An attachment circuit's " +
                  "operational state";
    }
  }
  augment "/l2vpn-state/l2vpn-instances-state/l2vpn-instance/endpoint/ac-or-pw-or-redundancy-grp-choice/redundancy-grp-case/" +
          "backup-choice/backup-pw-case" {
    description "Augment of backup pseudowire state";
    list backup-pw {
      uses common-pw-state-grp;
      description "A pseudowire's operational state";
    }
  }

  /* Used by L2VPN Provider */

  augment "/l2vpn/pw-templates/pw-template" {
    description "Augments additional fields to pw-template";
    ext:augment-identifier "pw-template-aug";
    leaf encapsulation {
      type enumeration {
        enum "mpls" {
          description "MPLS encapsulation";
        }
        enum "l2tp" {
          description "L2TP encapsulation";
        }
      }
    }
  }

  augment "/l2vpn/l2vpn-instances/l2vpn-instance" {
    description "Tenant augmentation adds tenant attributes to l2vpn-instance.";
    ext:augment-identifier "tenant-aug";
    leaf tenant-id {
      type string;
      description "Tenant ID";
    }
  }

  augment "/l2vpn/l2vpn-instances/l2vpn-instance/endpoint" {
    description "PE augmentation identifies Provider Edge which connects Customer Edge.";
    ext:augment-identifier "pe-aug";
    leaf pe-node-id {
      type nt:node-id;
      description "Provider Edge node-id from network-topology:network-topology/topology/l2vpn-pe/node/<node-id>.";
    }

    leaf pe-2-ce-tp-id {
      type nt:tp-id;
      description "Termination point on Provider Edge which connects Customer Edge.";
    }
  }

  typedef status {
    description "A type describing the status of L3VPN processing by provider.";
    type enumeration {
      enum complete {
        value 0;
        description "L2VPN processing completed successfully.";
      }
      enum commit-failed-rollback-complete {
        value -1;
        description "L2VPN processing did not complete successfully and rollback completed
                successfully.";
      }
      enum inconsistent {
        value -2;
        description "L2VPN processing and rollback did not complete successfully or other error occured.";
      }
    }
  }

  /* RPCs */

  rpc commit-l2vpn {
    description "Reads intended l2vpn from config datastore, real l2vpn from operational datastore and starts network element configuration.
      Output is returned after network elements are configured or an error occured.";
    output {
      leaf status {
        type status;
      }
      leaf error-message {
        type string;
      }
    }
  }
}
